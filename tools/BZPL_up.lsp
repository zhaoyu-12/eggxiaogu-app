;;; BZPL.lsp - 闭合多段线外侧对齐标注 最终版
;;; 功能: ①自动新建标注图层(可命名) ②文字方向可选(随线/水平) ③标注位置可选内侧/外侧(逐段判定, 凹多边形正确) ④文字统一在尺寸线上方(DIMTAD) ⑤全中文提示
;;; 命令: BZPL   (GBK编码, CAD2014/天正直接加载)
(defun get-verts8 (ent / elist pts v)
  (setq elist (entget ent))
  (cond
    ((= (cdr (assoc 0 elist)) "LWPOLYLINE")
     (foreach v elist
       (if (= (car v) 10)
         (setq pts (append pts (list (list (cadr v) (caddr v) 0.0))))
       )
     )
    )
    ((= (cdr (assoc 0 elist)) "POLYLINE")
     (setq v (entnext ent))
     (while (and v (= (cdr (assoc 0 (entget v))) "VERTEX"))
       (setq elist (entget v))
       (if (/= 16 (logand 16 (cdr (assoc 70 elist))))
         (setq pts (append pts (list (cdr (assoc 10 elist)))))
       )
       (setq v (entnext v))
     )
    )
  )
  pts
)
(defun pt-in-poly8 (pt verts / i n p1 p2 x y xi yi xj yj c)
  ;; 标准射线法: 严格异或跨越判定
  (setq x (car pt) y (cadr pt) c nil i 0 n (length verts))
  (while (< i n)
    (setq p1 (nth i verts))
    (setq p2 (nth (if (= (1+ i) n) 0 (1+ i)) verts))
    (setq xi (car p1) yi (cadr p1))
    (setq xj (car p2) yj (cadr p2))
    (if (or (and (<= yi y) (> yj y)) (and (> yi y) (<= yj y)))
      (if (< x (+ xi (/ (* (- y yi) (- xj xi)) (- yj yi))))
        (setq c (not c))
      )
    )
    (setq i (1+ i))
  )
  c
)
(defun c:BZPL ( / ent verts n i p1 p2 mid ang pt3 h layans layname oldtih oldtoh dirans side invar oldtad)
  (setq ent (car (entsel "\n请选择闭合多段线: ")))
  (if (null ent) (progn (princ "\n未选中对象, 退出。") (exit)))
  (setq verts (get-verts8 ent))
  (if (null verts) (progn (princ "\n读取顶点失败: 请选PLINE多段线。") (exit)))
  (setq n (length verts))
  (princ (strcat "\n已读取顶点数: " (itoa n)))
  (initget "Y N")
  (setq layans (getkword "\n是否自动新建标注图层[是(Y)/否(N)] <Y>: "))
  (if (null layans) (setq layans "Y"))
  (if (= layans "Y")
    (progn
      (setq layname (getstring T "\n新图层名称<标注-线长>: "))
      (if (= layname "") (setq layname "标注-线长"))
      (if (null (tblsearch "LAYER" layname))
        (command "_.-LAYER" "_N" layname "" "_C" "1" layname "")
      )
      (if (tblsearch "LAYER" layname)
        (progn
          (setvar "CLAYER" layname)
          (princ (strcat "\n图层已就绪: " layname))
        )
        (progn
          (command "_.-LAYER" "_S" layname "")
          (princ (strcat "\n图层已置当前(-LAYER方式): " layname))
        )
      )
    )
    (princ (strcat "\n使用当前图层: " (getvar "CLAYER")))
  )
  (initget "A H")
  (setq dirans (getkword "\n文字方向[随线段(A)/全部水平(H)] <A>: "))
  (if (null dirans) (setq dirans "A"))
  (setq oldtih (getvar "DIMTIH") oldtoh (getvar "DIMTOH") oldtad (getvar "DIMTAD"))
  (setvar "DIMTAD" 1)
  (if (= dirans "H")
    (progn (setvar "DIMTIH" 1) (setvar "DIMTOH" 1))
    (progn (setvar "DIMTIH" 0) (setvar "DIMTOH" 0))
  )
  (initget "I W")
  (setq side (getkword "\n标注位置[内侧(I)/外侧(W)] <W>: "))
  (if (null side) (setq side "W"))
  (setq h (getreal "\n标注偏移距离<图上单位, 默认500>: "))
  (if (null h) (setq h 500.0))
  (setvar "CMDECHO" 0)
  (setq i 0)
  (while (< i n)
    (setq p1 (nth i verts))
    (setq p2 (nth (if (= (1+ i) n) 0 (1+ i)) verts))
    (setq mid (mapcar '(lambda (a b) (/ (+ a b) 2.0)) p1 p2))
    (setq ang (- (angle p1 p2) (/ pi 2.0)))
    (setq pt3 (polar mid ang h))
    (setq invar (pt-in-poly8 pt3 verts))
    (if (if (= side "W") invar (not invar))
      (progn (setq ang (+ (angle p1 p2) (/ pi 2.0)))
             (setq pt3 (polar mid ang h)))
    )
    (command "_.DIMALIGNED" "_non" p1 "_non" p2 "_non" pt3)
    (setq i (1+ i))
  )
  (setvar "DIMTIH" oldtih)
  (setvar "DIMTOH" oldtoh)
  (setvar "DIMTAD" oldtad)
  (setvar "CMDECHO" 1)
  (princ (strcat "\n完成: 共 " (itoa n) " 段, 全部" (if (= side "W") "外侧" "内侧") "。"))
  (princ)
)
(princ "\nBZPL 已加载。命令: BZPL")
