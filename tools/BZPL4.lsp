;;; BZPL4.lsp —— 闭合多段线外侧对齐标注(兼容版: 不依赖ActiveX, LWPOLYLINE/老式POLYLINE通吃)
;;; 命令: BZPL4
(vl-load-com)
(defun get-verts (ent / elist pts v)
  ;; 从组码读顶点, 兼容LWPOLYLINE(10码平面)与经典POLYLINE(子实体VERTEX)
  (setq elist (entget ent))
  (cond
    ((= (cdr (assoc 0 elist)) "LWPOLYLINE")
     (foreach v elist
       (if (= (car v) 10)
         (setq pts (append pts (list (list (cadr v) (caddr v) 0.0))))
       )
     )
    )
    ((= (cdr (assoc 0 elist)) "POLYLINE")
     (setq v (entnext ent))
     (while (and v (= (cdr (assoc 0 (entget v))) "VERTEX"))
       (setq elist (entget v))
       (if (/= 16 (logand 16 (cdr (assoc 70 elist))))  ;; 跳过样条拟合控制点
         (setq pts (append pts (list (cdr (assoc 10 elist)))))
       )
       (setq v (entnext v))
     )
    )
  )
  pts
)
(defun c:BZPL4 ( / ent verts n i p1 p2 mid ang pt3 h sa x1 y1 x2 y2 olderr)
  (setq ent (car (entsel "\n选择多段线: ")))
  (if (null ent) (progn (princ "\n未选中对象。") (exit)))
  (setq verts (get-verts ent))
  (if (null verts)
    (progn (princ "\n读取顶点失败: 请确认选的是PLINE多段线(命令PL画的), 不是直线或天正专有对象。") (exit))
  )
  (setq n (length verts))
  (princ (strcat "\n读取到 " (itoa n) " 个顶点。"))
  ;; 鞋带方向
  (setq sa 0.0 i 0)
  (while (< i n)
    (setq p1 (nth i verts))
    (setq p2 (nth (if (= (1+ i) n) 0 (1+ i)) verts))
    (setq x1 (car p1) y1 (cadr p1) x2 (car p2) y2 (cadr p2))
    (setq sa (+ sa (- (* x1 y2) (* x2 y1))))
    (setq i (1+ i))
  )
  (setq h (getreal "\n标注偏移高度<图上单位>: "))
  (if (null h) (setq h 500.0))
  (setvar "CMDECHO" 0)
  (setq i 0)
  (while (< i n)
    (setq p1 (nth i verts))
    (setq p2 (nth (if (= (1+ i) n) 0 (1+ i)) verts))
    (setq mid (mapcar '(lambda (a b) (/ (+ a b) 2.0)) p1 p2))
    (if (> sa 0.0)
      (setq ang (- (angle p1 p2) (/ pi 2.0)))
      (setq ang (+ (angle p1 p2) (/ pi 2.0)))
    )
    (setq pt3 (polar mid ang h))
    (command "_.DIMALIGNED" "_non" p1 "_non" p2 "_non" pt3)
    (setq i (1+ i))
  )
  (setvar "CMDECHO" 1)
  (princ (strcat "\n完成: " (itoa n) " 段, 走向" (if (> sa 0.0) "逆时针" "顺时针") ", 全部外侧。"))
  (princ)
)
(princ "\nBZPL4.lsp 已加载, 命令: BZPL4 (兼容天正/CASS环境)")
