;;; BZPL3.lsp —— 闭合多段线逐段对齐标注, 自动判方向, 统一标在外侧
;;; 命令: BZPL3, 选闭合多段线, 输偏移高度(图上单位)
(vl-load-com)
(defun c:BZPL3 ( / ent obj coords n i p1 p2 mid ang pt3 h sa j x1 y1 x2 y2)
  (setq ent (car (entsel "\n选择闭合多段线: ")))
  (if ent
    (progn
      (setq obj (vlax-ename->vla-object ent))
      (setq coords (vlax-get obj 'Coordinates))
      (setq n (/ (length coords) 2))
      ;; 鞋带公式算方向: sa>0 逆时针, sa<0 顺时针
      (setq sa 0.0)
      (setq i 0)
      (while (< i n)
        (setq x1 (nth (* 2 i) coords))
        (setq y1 (nth (1+ (* 2 i)) coords))
        (if (< (1+ i) n)
          (progn (setq x2 (nth (* 2 (1+ i)) coords)) (setq y2 (nth (1+ (* 2 (1+ i))) coords)))
          (progn (setq x2 (nth 0 coords)) (setq y2 (nth 1 coords)))
        )
        (setq sa (+ sa (- (* x1 y2) (* x2 y1))))
        (setq i (1+ i))
      )
      (setq h (getreal "\n标注偏移高度<图上单位, 如500>: "))
      (if (null h) (setq h 500.0))
      (setq i 0)
      (while (< i n)
        (setq p1 (list (nth (* 2 i) coords) (nth (1+ (* 2 i)) coords) 0.0))
        (if (< (1+ i) n)
          (setq p2 (list (nth (* 2 (1+ i)) coords) (nth (1+ (* 2 (1+ i))) coords) 0.0))
          (setq p2 (list (nth 0 coords) (nth 1 coords) 0.0))
        )
        (setq mid (mapcar '(lambda (a b) (/ (+ a b) 2.0)) p1 p2))
        ;; CCW: 外侧=左转90°的相反方向 → 右转90°(ang - pi/2)
        ;; CW : 外侧=左转90°
        (if (> sa 0.0)
          (setq ang (- (angle p1 p2) (/ pi 2.0)))
          (setq ang (+ (angle p1 p2) (/ pi 2.0)))
        )
        (setq pt3 (polar mid ang h))
        (command "_.DIMALIGNED" "_non" p1 "_non" p2 "_non" pt3)
        (setq i (1+ i))
      )
      (princ (strcat "\n完成, 共标注 " (itoa n) " 段, 方向判定: " (if (> sa 0.0) "逆时针" "顺时针")))
    )
  )
  (princ)
)
(princ "\nBZPL3.lsp 已加载, 命令: BZPL3 (闭合线外侧标注版)")
