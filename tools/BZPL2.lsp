;;; BZPL2.lsp —— 多段线逐段标数字(轻量文字版, 不出尺寸线) + 末尾报总长
;;; 命令: BZPL2, 选多段线, 输字高(默认3.5, 图纸单位)
(vl-load-com)
(defun c:BZPL2 ( / ent obj coords n i p1 p2 mid ang pt h txt total angd)
  (setq ent (car (entsel "\n选择多段线: ")))
  (if ent
    (progn
      (setq obj (vlax-ename->vla-object ent))
      (setq coords (vlax-get obj 'Coordinates))
      (setq n (/ (length coords) 2))
      (if (equal (vlax-get obj 'Closed) :vlax-true) (setq n (1- n)))
      (setq h (getreal "\n文字高度<3.5>: "))
      (if (null h) (setq h 3.5))
      (setq i 0 total 0.0)
      (while (< i n)
        (setq p1 (list (nth (* 2 i) coords) (nth (1+ (* 2 i)) coords) 0.0))
        (if (< (1+ i) n)
          (setq p2 (list (nth (* 2 (1+ i)) coords) (nth (1+ (* 2 (1+ i))) coords) 0.0))
          (setq p2 (list (nth 0 coords) (nth 1 coords) 0.0))
        )
        (setq seglen (distance p1 p2))
        (setq total (+ total seglen))
        (setq mid (mapcar '(lambda (a b) (/ (+ a b) 2.0)) p1 p2))
        (setq ang (angle p1 p2))
        (setq angd ang)
        ;; 保持文字不倒置
        (if (and (> angd (* 0.5 pi)) (<= angd (* 1.5 pi))) (setq angd (+ angd pi)))
        (setq pt (polar mid (+ ang (* 0.5 pi)) (* h 1.2)))
        (command "_.TEXT" "_non" (trans pt 0 1) h (cvunit angd "radian" "degree") (rtos seglen 2 0))
        (setq i (1+ i))
      )
      (princ (strcat "\n共 " (itoa n) " 段, 总长 = " (rtos total 2 2)))
    )
  )
  (princ)
)
(princ "\nBZPL2.lsp 已加载, 命令: BZPL2")
